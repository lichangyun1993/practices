module practice {
    yang-version 1;
    namespace "urn:opendaylight:params:xml:ns:yang:practice";
    prefix "practice";

    revision "2018-08-14" {
        description "Initial revision of practice model";
    }
    container data-model {
    	 leaf name {
    		type string;
    	}
    }
    
    rpc greet {
        input {
            leaf lf-input {
                type string;
            }
        }
        output {
            leaf lf-output {
                type string;
            }
        }
    }
    
    notification greet-message {
    	 leaf message {
    	 	type string;
    	 }
    }
}
